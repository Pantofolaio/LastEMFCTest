# HVAC Requirements

# Specification: Specification Document
- Description: Requirements Document

## REQ-1
In the Automode the system must realize a two zone climate control
- Status: accepted

## REQ-2
In the Manualmode the system must realize a one zone climate control
- Status: accepted

## REQ-3
The system must control a blower depending on the controller
- Status: accepted

## REQ-4
The temperature must be read with a accuracy of 0.1°C, using an external Sensor
- Status: accepted

## REQ-5
The user handling of the system must be able by using an interface for a external user interface
- Status: accepted

## REQ-6
The user handling of the system must be able by using a Display directly connected to the system
- Status: accepted

## REQ-7
The system must implement either [REQ-5] or [REQ-6].
- Status: new
